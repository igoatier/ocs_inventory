GWSMTPMIB DEFINITIONS ::= BEGIN

IMPORTS
        Counter, TimeTicks, Gauge, enterprises  FROM RFC1155-SMI
        DisplayString                           FROM RFC1213-MIB
        TRAP-TYPE                               FROM RFC-1215
        OBJECT-TYPE                             FROM RFC-1212;

novell          OBJECT IDENTIFIER   ::= { enterprises  23 }
gateways        OBJECT IDENTIFIER   ::= { novell        2 }
gwsmtp          OBJECT IDENTIFIER   ::= { gateways     51 }
gwsmtpInfo      OBJECT IDENTIFIER   ::= { gwsmtp        1 }
gwsmtpTrapInfo  OBJECT IDENTIFIER   ::= { gwsmtp        2 }
gwsmtpTraps     OBJECT IDENTIFIER   ::= { gwsmtp        3 }


-- ================================= GWSMTP GWE Get/Set Variables =========
gwsmtpGatewayName OBJECT-TYPE
       SYNTAX  DisplayString (SIZE (0..255))
       ACCESS  read-only
       STATUS  mandatory
       DESCRIPTION
       "The GroupWise SMTP Gateway name."
   ::= { gwsmtpInfo 1 }
 
gwsmtpTimeUp OBJECT-TYPE
       SYNTAX  TimeTicks
       ACCESS  read-only
       STATUS  mandatory
       DESCRIPTION
      "Uptime of the GroupWise SMTP Gateway."
   ::= { gwsmtpInfo 2 }

gwsmtpLinkGroupWise OBJECT-TYPE
       SYNTAX  DisplayString (SIZE (0..5))
       ACCESS  read-only
       STATUS  mandatory
       DESCRIPTION
      "GroupWise SMTP Gateway Link: UP or DOWN"
   ::= { gwsmtpInfo 3 }

gwsmtpLinkFrgn OBJECT-TYPE
       SYNTAX  DisplayString (SIZE (0..5))
       ACCESS  read-only
       STATUS  mandatory
       DESCRIPTION
      "GroupWise SMTP Gateway Foreign Link: UP or DOWN"
   ::= { gwsmtpInfo 4 }

gwsmtpStatBytesOut OBJECT-TYPE
       SYNTAX  Counter
       ACCESS  read-only
       STATUS  mandatory
       DESCRIPTION
      "The number of message bytes sent to GroupWise SMTP."
   ::= { gwsmtpInfo 5 }
 
gwsmtpStatBytesIn OBJECT-TYPE
       SYNTAX  Counter
       ACCESS  read-only
       STATUS  mandatory
       DESCRIPTION
      "The number of message bytes received from GroupWise SMTP."
   ::= { gwsmtpInfo 6 }
 
gwsmtpStatMsgsOut OBJECT-TYPE
       SYNTAX  Counter
       ACCESS  read-only
       STATUS  mandatory
       DESCRIPTION
      "The number of messages sent to GroupWise SMTP."
   ::= { gwsmtpInfo 7 }
 
gwsmtpStatMsgsIn OBJECT-TYPE
       SYNTAX  Counter
       ACCESS  read-only
       STATUS  mandatory
       DESCRIPTION
      "The number of messages received from SMTP."
   ::= { gwsmtpInfo 8 }
 
gwsmtpStatStatusesOut OBJECT-TYPE
       SYNTAX  Counter
       ACCESS  read-only
       STATUS  mandatory
       DESCRIPTION
      "The number of statuses sent to SMTP."
   ::= { gwsmtpInfo 9 }
 
gwsmtpStatStatusesIn OBJECT-TYPE
       SYNTAX  Counter
       ACCESS  read-only
       STATUS  mandatory
       DESCRIPTION
      "The number of statuses received from SMTP."
   ::= { gwsmtpInfo 10 }
 
gwsmtpStatErrorsOut OBJECT-TYPE
       SYNTAX  Counter
       ACCESS  read-only
       STATUS  mandatory
       DESCRIPTION
      "The number of failed transfers to SMTP."
   ::= { gwsmtpInfo 11 }
 
gwsmtpStatErrorsIn OBJECT-TYPE
       SYNTAX  Counter
       ACCESS  read-only
       STATUS  mandatory
       DESCRIPTION
      "The number of failed transfers from SMTP."
   ::= { gwsmtpInfo 12 }

gwsmtpStatTimeReset OBJECT-TYPE
       SYNTAX  TimeTicks
       ACCESS  read-only
       STATUS  mandatory
       DESCRIPTION
      "Time since statistics were reset on SMTP Gateway."
   ::= { gwsmtpInfo 13 }

gwsmtpQueueWpcsout OBJECT-TYPE
       SYNTAX  Counter
       ACCESS  read-only
       STATUS  mandatory
       DESCRIPTION
      "The number of messages to be processed by SMTP (WPCSOUT)."
   ::= { gwsmtpInfo 14 }

gwsmtpQueueWpcsin OBJECT-TYPE
       SYNTAX  Counter
       ACCESS  read-only
       STATUS  mandatory
       DESCRIPTION
      "The number of messages to be processed by GroupWise Message Server (WPCSIN)."
   ::= { gwsmtpInfo 15 }

gwsmtpQueueGwhold OBJECT-TYPE
       SYNTAX  Counter
       ACCESS  read-only
       STATUS  mandatory
       DESCRIPTION
      "The number messages holding for later processing by SMTP (GWHOLD)."
   ::= { gwsmtpInfo 16 }

gwsmtpQueueGwprob OBJECT-TYPE
       SYNTAX  Counter
       ACCESS  read-only
       STATUS  mandatory
       DESCRIPTION
      "The number messages in SMTP's problem directory (GWPROB)."
   ::= { gwsmtpInfo 17 }

gwsmtpStatInterval OBJECT-TYPE
       SYNTAX  TimeTicks
       ACCESS  read-only
       STATUS  mandatory
       DESCRIPTION
      "Statistics interval for the GroupWise SMTP Gateway."
   ::= { gwsmtpInfo 18 }

gwsmtpStatIntervalMsgsOut OBJECT-TYPE
       SYNTAX  Counter
       ACCESS  read-only
       STATUS  mandatory
       DESCRIPTION
      "The number of messages sent to GroupWise SMTP in statistics interval."
   ::= { gwsmtpInfo 19 }
 
gwsmtpStatIntervalMsgsIn OBJECT-TYPE
       SYNTAX  Counter
       ACCESS  read-only
       STATUS  mandatory
       DESCRIPTION
      "The number of messages received from SMTP in statistics interval."
   ::= { gwsmtpInfo 20 }
 
gwsmtpStatIntervalStatusesOut OBJECT-TYPE
       SYNTAX  Counter
       ACCESS  read-only
       STATUS  mandatory
       DESCRIPTION
      "The number of statuses sent to SMTP in statistics interval."
   ::= { gwsmtpInfo 21 }
 
gwsmtpStatIntervalStatusesIn OBJECT-TYPE
       SYNTAX  Counter
       ACCESS  read-only
       STATUS  mandatory
       DESCRIPTION
      "The number of statuses received from SMTP in statistics interval."
   ::= { gwsmtpInfo 22 }
 
gwsmtpStatIntervalErrorsOut OBJECT-TYPE
       SYNTAX  Counter
       ACCESS  read-only
       STATUS  mandatory
       DESCRIPTION
      "The number of failed transfers to SMTP in statistics interval."
   ::= { gwsmtpInfo 23 }
 
gwsmtpStatIntervalErrorsIn OBJECT-TYPE
       SYNTAX  Counter
       ACCESS  read-only
       STATUS  mandatory
       DESCRIPTION
      "The number of failed transfers from SMTP in statistics interval."
   ::= { gwsmtpInfo 24 }

gwsmtpQThresholdCheckInterval OBJECT-TYPE
       SYNTAX  Counter
       ACCESS  read-write
       STATUS  mandatory
       DESCRIPTION
      "The number of minutes between directory scans or directory threshold traps for SMTP."
   ::= { gwsmtpInfo 25 }

gwsmtpQThresholdWpcsout OBJECT-TYPE
       SYNTAX  Counter
       ACCESS  read-write
       STATUS  mandatory
       DESCRIPTION
      "The number of messages waiting for SMTP gateway before firing threshold trap (WPCSOUT)."
   ::= { gwsmtpInfo 26 }

gwsmtpQThresholdWpcsin OBJECT-TYPE
       SYNTAX  Counter
       ACCESS  read-write
       STATUS  mandatory
       DESCRIPTION
      "The number of messages waiting for Message Server from SMTP before firing threshold trap (WPCSIN)."
   ::= { gwsmtpInfo 27 }

gwsmtpQThresholdGwhold OBJECT-TYPE
       SYNTAX  Counter
       ACCESS  read-write
       STATUS  mandatory
       DESCRIPTION
      "The number of defered messages waiting for SMTP gateway before firing threshold trap (GWHOLD)."
   ::= { gwsmtpInfo 28 }

gwsmtpQThresholdGwprob OBJECT-TYPE
       SYNTAX  Counter
       ACCESS  read-write
       STATUS  mandatory
       DESCRIPTION
      "The number of problem messages SMTP gateway moved before firing threshold trap (GWPROB)."
   ::= { gwsmtpInfo 29 }

gwsmtpThresholdMsgSizeIn OBJECT-TYPE
       SYNTAX  Counter
       ACCESS  read-write
       STATUS  mandatory
       DESCRIPTION
      "The max size of an incoming message the SMTP gateway can process before firing threshold trap."
   ::= { gwsmtpInfo 30 }

gwsmtpThresholdMsgSizeOut OBJECT-TYPE
       SYNTAX  Counter
       ACCESS  read-write
       STATUS  mandatory
       DESCRIPTION
      "The max size of an outgoing message the SMTP gateway can process before firing threshold trap."
   ::= { gwsmtpInfo 31 }

gwsmtpActionResetStats OBJECT-TYPE
       SYNTAX  INTEGER {
       reset(1)
}
       ACCESS  write-only
       STATUS  mandatory
       DESCRIPTION
      "Reset the SMTP gateway statistics."
   ::= { gwsmtpInfo 32 }

gwsmtpActionRestartGateway OBJECT-TYPE
       SYNTAX  INTEGER {
       restart(1)
}
       ACCESS  write-only
       STATUS  mandatory
       DESCRIPTION
      "Restart the SMTP gateway."
   ::= { gwsmtpInfo 33 }




-- ============================= GWSMTP specific Get/Set Variables =========

gwsmtpdThreadsAvailSend OBJECT-TYPE
       SYNTAX  Counter
       ACCESS  read-only
       STATUS  mandatory
       DESCRIPTION
      "The number of SMTP Daemon send threads available."
   ::= { gwsmtpInfo 48 }

gwsmtpdThreadsAvailReceive OBJECT-TYPE
       SYNTAX  Counter
       ACCESS  read-only
       STATUS  mandatory
       DESCRIPTION
      "The number of SMTP Daemon receive threads available."
   ::= { gwsmtpInfo 49 }


gwsmtpdThreadsActiveSend OBJECT-TYPE
       SYNTAX  Counter
       ACCESS  read-only
       STATUS  mandatory
       DESCRIPTION
      "The number of SMTP Daemon send threads active."
   ::= { gwsmtpInfo 50 }


gwsmtpdThreadsActiveReceive OBJECT-TYPE
       SYNTAX  Counter
       ACCESS  read-only
       STATUS  mandatory
       DESCRIPTION
      "The number of SMTP Daemon receive threads active."
   ::= { gwsmtpInfo 51 }


gwsmtpdErrorsMXLookup OBJECT-TYPE
       SYNTAX  Counter
       ACCESS  read-only
       STATUS  mandatory
       DESCRIPTION
      "The number of SMTP Daemon DNS MX lookup errors."
   ::= { gwsmtpInfo 52 }


gwsmtpdErrorsHostsUnknown OBJECT-TYPE
       SYNTAX  Counter
       ACCESS  read-only
       STATUS  mandatory
       DESCRIPTION
      "The number of SMTP Daemon unknown destination hosts."
   ::= { gwsmtpInfo 53 }


gwsmtpdErrorsHostsDown OBJECT-TYPE
       SYNTAX  Counter
       ACCESS  read-only
       STATUS  mandatory
       DESCRIPTION
      "The number of SMTP Daemon TCP/IP connect errors."
   ::= { gwsmtpInfo 54 }


gwsmtpdErrorsTCPRead OBJECT-TYPE
       SYNTAX  Counter
       ACCESS  read-only
       STATUS  mandatory
       DESCRIPTION
      "The number of SMTP Daemon TCP/IP read errors."
   ::= { gwsmtpInfo 55 }


gwsmtpdErrorsTCPWrite OBJECT-TYPE
       SYNTAX  Counter
       ACCESS  read-only
       STATUS  mandatory
       DESCRIPTION
      "The number of SMTP Daemon TCP/IP write errors."
   ::= { gwsmtpInfo 56 }


gwsmtpdMessagesIn OBJECT-TYPE
       SYNTAX  Counter
       ACCESS  read-only
       STATUS  mandatory
       DESCRIPTION
      "The number of SMTP Daemon messages received."
   ::= { gwsmtpInfo 57 }


gwsmtpdMessagesOut OBJECT-TYPE
       SYNTAX  Counter
       ACCESS  read-only
       STATUS  mandatory
       DESCRIPTION
      "The number of SMTP Daemon messages sent."
   ::= { gwsmtpInfo 58 }

gwsmtpQThresholdSend OBJECT-TYPE
       SYNTAX  Counter
       ACCESS  read-write
       STATUS  mandatory
       DESCRIPTION
      "The number of send messages SMTP gateway can queue to daemon before firing threshold trap (SEND)."
   ::= { gwsmtpInfo 59 }

gwsmtpQThresholdReceive OBJECT-TYPE
       SYNTAX  Counter
       ACCESS  read-write
       STATUS  mandatory
       DESCRIPTION
      "The number of messages queued by daemon for SMTP gateway before firing threshold trap (RECEIVE)."
   ::= { gwsmtpInfo 60 }

gwsmtpQThresholdDefer OBJECT-TYPE
       SYNTAX  Counter
       ACCESS  read-write
       STATUS  mandatory
       DESCRIPTION
      "The number of messages to have daemon retry sending for SMTP gateway before firing threshold trap (DEFER)."
   ::= { gwsmtpInfo 61 }

gwsmtpQueueSend OBJECT-TYPE
       SYNTAX  Counter
       ACCESS  read-only
       STATUS  mandatory
       DESCRIPTION
      "The number of messages queued to daemon for SMTP gateway (SEND)."
   ::= { gwsmtpInfo 62 }

gwsmtpQueueReceive OBJECT-TYPE
       SYNTAX  Counter
       ACCESS  read-only
       STATUS  mandatory
       DESCRIPTION
      "The number of messages queued to SMTP gateway from daemon (RECEIVE)."
   ::= { gwsmtpInfo 63 }

gwsmtpQueueDefer OBJECT-TYPE
       SYNTAX  Counter
       ACCESS  read-only
       STATUS  mandatory
       DESCRIPTION
      "The number of messages queued to retry for daemon on SMTP gateway (DEFER)."
   ::= { gwsmtpInfo 64 }




-- ================================================== gwsmtpTrapInfo ========
-- The gwsmtpTrapInfo group
-- These objects are used only in traps produced by GWSMTP
 
gwsmtpTrapTime OBJECT-TYPE
		SYNTAX  INTEGER
		ACCESS  not-accessible
		STATUS  mandatory
		DESCRIPTION "The time the trap occurred. Seconds since Jan 1, 1970 (GMT)"
	::= { gwsmtpTrapInfo 1 }

gwsmtpTrapDomainName OBJECT-TYPE
       SYNTAX  DisplayString (SIZE (0..255))
       ACCESS  not-accessible
       STATUS  mandatory
       DESCRIPTION "The Domain for which this gateway operates."
   ::= { gwsmtpTrapInfo 2 }

 
-- ============================================== GWSMTP GWE Traps =========
gwsmtpStartTrap TRAP-TYPE
		ENTERPRISE    gwsmtpTraps
		VARIABLES     {gwsmtpTrapTime, gwsmtpGatewayName}
		DESCRIPTION   "GroupWise SMTP Gateway start."
		--NMS Trap annotation
		--#TYPE       "GroupWise SMTP Gateway start."
		--#SUMMARY    "GroupWise SMTP Gateway %s has started."
		--#ARGUMENTS  {1}
		--#SEVERITY   INFORMATIONAL
		--#TIMEINDEX  0
		--#STATE      OPERATIONAL
		::= 1

gwsmtpStopTrap TRAP-TYPE
		ENTERPRISE    gwsmtpTraps
		VARIABLES     {gwsmtpTrapTime, gwsmtpGatewayName}
		DESCRIPTION   "GroupWise SMTP Gateway stop."
		--NMS Trap annotation
		--#TYPE       "GroupWise SMTP Gateway stop."
		--#SUMMARY    "GroupWise SMTP Gateway %s has stopped."
		--#ARGUMENTS  {1}
		--#SEVERITY   CRITICAL
		--#TIMEINDEX  0
		--#STATE      NONOPERATIONAL
		::= 2

gwsmtpRestartTrap TRAP-TYPE
		ENTERPRISE    gwsmtpTraps
		VARIABLES     {gwsmtpTrapTime, gwsmtpGatewayName}
		DESCRIPTION   "GroupWise SMTP Gateway restart."
		--NMS Trap annotation
		--#TYPE       "GroupWise SMTP Gateway restart."
		--#SUMMARY    "GroupWise SMTP Gateway %s has been restarted."
		--#ARGUMENTS  {1}
		--#SEVERITY   INFORMATIONAL
		--#TIMEINDEX  0
		--#STATE      OPERATIONAL
		::= 3
 
gwsmtpGroupWiseLinkTrap TRAP-TYPE
		ENTERPRISE    gwsmtpTraps
		VARIABLES     {gwsmtpTrapTime, gwsmtpGatewayName}
		DESCRIPTION   "GroupWise Link lost by GroupWise SMTP Gateway"
		--NMS Trap annotation
		--#TYPE       "GroupWise Link lost by GroupWise SMTP Gateway"
		--#SUMMARY    "GroupWise SMTP Gateway %s has lost its GroupWise Link"
		--#ARGUMENTS  {1}
		--#SEVERITY   INFORMATIONAL
		--#TIMEINDEX  0
		--#STATE      OPERATIONAL
		::= 4

gwsmtpMovedToProbTrap TRAP-TYPE
		ENTERPRISE    gwsmtpTraps
		VARIABLES     {gwsmtpTrapTime, gwsmtpGatewayName}
		DESCRIPTION   "Problem message moved to GWPROB directory for SMTP gateway"
		--NMS Trap annotation
		--#TYPE       "Problem message moved to GWPROB directory for SMTP gateway"
		--#SUMMARY    "GroupWise SMTP Gateway %s moved a problem message to GWPROB"
		--#ARGUMENTS  {1}
		--#SEVERITY   INFORMATIONAL
		--#TIMEINDEX  0
		--#STATE      OPERATIONAL
		::= 6

gwsmtpWpcsoutThreshTrap TRAP-TYPE
		ENTERPRISE    gwsmtpTraps
		VARIABLES     {gwsmtpTrapTime, gwsmtpGatewayName}
		DESCRIPTION   "Threshold for messages to be processed by SMTP gateway has been exceeded (WPCSOUT)"
		--NMS Trap annotation
		--#TYPE       "Threshold for messages to be processed by SMTP gateway has been exceeded (WPCSOUT)"
		--#SUMMARY    "GroupWise SMTP Gateway %s has exceeded its threshold for messages to be processed (WPCSOUT)"
		--#ARGUMENTS  {1}
		--#SEVERITY   INFORMATIONAL
		--#TIMEINDEX  0
		--#STATE      OPERATIONAL
		::= 7

gwsmtpWpcsinThreshTrap TRAP-TYPE
		ENTERPRISE    gwsmtpTraps
		VARIABLES     {gwsmtpTrapTime, gwsmtpGatewayName}
		DESCRIPTION   "The threshold for processed messages by SMTP gateway has been exceeded (WPCSIN)"
		--NMS Trap annotation
		--#TYPE       "The threshold for processed messages by SMTP gateway has been exceeded (WPCSIN)"
		--#SUMMARY    "GroupWise SMTP Gateway %s has exceeded its threshold for processed messages (WPCSIN)"
		--#ARGUMENTS  {1}
		--#SEVERITY   INFORMATIONAL
		--#TIMEINDEX  0
		--#STATE      OPERATIONAL
		::= 8

gwsmtpGwholdThreshTrap TRAP-TYPE
		ENTERPRISE    gwsmtpTraps
		VARIABLES     {gwsmtpTrapTime, gwsmtpGatewayName}
		DESCRIPTION   "The threshold for defered messages in hold area for SMTP gateway has been exceeded (GWHOLD)"
		--NMS Trap annotation
		--#TYPE       "The threshold for defered messages in hold area for SMTP gateway has been exceeded (GWHOLD)"
		--#SUMMARY    "GroupWise SMTP Gateway %s has exceeded its threshold for defered messages (GWHOLD)"
		--#ARGUMENTS  {1}
		--#SEVERITY   INFORMATIONAL
		--#TIMEINDEX  0
		--#STATE      OPERATIONAL
		::= 9

gwsmtpGwprobThreshTrap TRAP-TYPE
		ENTERPRISE    gwsmtpTraps
		VARIABLES     {gwsmtpTrapTime, gwsmtpGatewayName}
		DESCRIPTION   "The threshold for problem messages in problem area for SMTP gateway has been exceeded (GWPROB)"
		--NMS Trap annotation
		--#TYPE       "The threshold for problem messages in problem area for SMTP gateway has been exceeded (GWPROB)"
		--#SUMMARY    "GroupWise SMTP Gateway %s has exceeded its threshold for problem messages (GWPROB)"
		--#ARGUMENTS  {1}
		--#SEVERITY   INFORMATIONAL
		--#TIMEINDEX  0
		--#STATE      OPERATIONAL
		::= 10


gwsmtpInSizeThreshTrap TRAP-TYPE
		ENTERPRISE    gwsmtpTraps
		VARIABLES     {gwsmtpTrapTime, gwsmtpGatewayName}
		DESCRIPTION   "The threshold for a incomming message for SMTP gateway has been exceeded"
		--NMS Trap annotation
		--#TYPE       "The threshold for a incomming message for SMTP gateway has been exceeded"
		--#SUMMARY    "GroupWise SMTP Gateway %s has exceeded its threshold for a incomming message"
		--#ARGUMENTS  {1}
		--#SEVERITY   INFORMATIONAL
		--#TIMEINDEX  0
		--#STATE      OPERATIONAL
		::= 11

gwsmtpOutSizeThreshTrap TRAP-TYPE
		ENTERPRISE    gwsmtpTraps
		VARIABLES     {gwsmtpTrapTime, gwsmtpGatewayName}
		DESCRIPTION   "The threshold for a outgoing message for SMTP gateway has been exceeded"
		--NMS Trap annotation
		--#TYPE       "The threshold for a outgoing message for SMTP gateway has been exceeded"
		--#SUMMARY    "GroupWise SMTP Gateway %s has exceeded its threshold for a outgoing message"
		--#ARGUMENTS  {1}
		--#SEVERITY   INFORMATIONAL
		--#TIMEINDEX  0
		--#STATE      OPERATIONAL
		::= 12




-- ======================================== GWSMTP specific Traps =========

gwsmtpReadErrorTrap TRAP-TYPE
		ENTERPRISE    gwsmtpTraps
		VARIABLES     {gwsmtpTrapTime, gwsmtpGatewayName}
		DESCRIPTION   "TCP/IP read error on GroupWise SMTP Gateway daemon"
		--NMS Trap annotation
		--#TYPE       "TCP/IP read error on GroupWise SMTP Gateway daemon"
		--#SUMMARY    "GroupWise SMTP Gateway %s had a TCP/IP read error - connection dropped"
		--#ARGUMENTS  {1}
		--#SEVERITY   INFORMATIONAL
		--#TIMEINDEX  0
		--#STATE      OPERATIONAL
		::= 32

gwsmtpWriteErrorTrap TRAP-TYPE
		ENTERPRISE    gwsmtpTraps
		VARIABLES     {gwsmtpTrapTime, gwsmtpGatewayName}
		DESCRIPTION   "TCP/IP write error on GroupWise SMTP Gateway daemon"
		--NMS Trap annotation
		--#TYPE       "TCP/IP write error on GroupWise SMTP Gateway daemon"
		--#SUMMARY    "GroupWise SMTP Gateway %s had a TCP/IP write error - connection dropped"
		--#ARGUMENTS  {1}
		--#SEVERITY   INFORMATIONAL
		--#TIMEINDEX  0
		--#STATE      OPERATIONAL
		::= 33

gwsmtpSendThreshTrap TRAP-TYPE
		ENTERPRISE    gwsmtpTraps
		VARIABLES     {gwsmtpTrapTime, gwsmtpGatewayName}
		DESCRIPTION   "The threshold for messages in daemon send area for SMTP gateway has been exceeded (SEND)"
		--NMS Trap annotation
		--#TYPE       "The threshold for messages in daemon send area for SMTP gateway has been exceeded (SEND)"
		--#SUMMARY    "GroupWise SMTP Gateway %s has exceeded its threshold for daemon send messages (SEND)"
		--#ARGUMENTS  {1}
		--#SEVERITY   INFORMATIONAL
		--#TIMEINDEX  0
		--#STATE      OPERATIONAL
		::= 34

gwsmtpReceiveThreshTrap TRAP-TYPE
		ENTERPRISE    gwsmtpTraps
		VARIABLES     {gwsmtpTrapTime, gwsmtpGatewayName}
		DESCRIPTION   "The threshold for messages in daemon receive area for SMTP gateway has been exceeded (RECEIVE)"
		--NMS Trap annotation
		--#TYPE       "The threshold for messages in daemon receive area for SMTP gateway has been exceeded (RECEIVE)"
		--#SUMMARY    "GroupWise SMTP Gateway %s has exceeded its threshold for received daemon messages (RECEIVE)"
		--#ARGUMENTS  {1}
		--#SEVERITY   INFORMATIONAL
		--#TIMEINDEX  0
		--#STATE      OPERATIONAL
		::= 35

gwsmtpDeferThreshTrap TRAP-TYPE
		ENTERPRISE    gwsmtpTraps
		VARIABLES     {gwsmtpTrapTime, gwsmtpGatewayName}
		DESCRIPTION   "The threshold for messages in daemon defer area for SMTP gateway has been exceeded (DEFER)"
		--NMS Trap annotation
		--#TYPE       "The threshold for messages in daemon defer area for SMTP gateway has been exceeded (DEFER)"
		--#SUMMARY    "GroupWise SMTP Gateway %s has exceeded its threshold for daemon defer messages (DEFER)"
		--#ARGUMENTS  {1}
		--#SEVERITY   INFORMATIONAL
		--#TIMEINDEX  0
		--#STATE      OPERATIONAL
		::= 36



END
