-- *********************************************
-- Modified by Garth K. Williams
-- Williams Technology Consulting Services
-- Date: 14Aug2002
-- *********************************************
--  Modified for compatability with SNMP4W2K PERFMIB
-- *********************************************


INTERNETSERVER-MIB DEFINITIONS ::= BEGIN

    IMPORTS
	enterprises, Counter, TimeTicks
	    FROM RFC1155-SMI
	OBJECT-TYPE
	    FROM RFC-1212
	DisplayString
	    FROM RFC1213-MIB
	microsoft, software
	    FROM MSFT-MIB;


--      microsoft       OBJECT IDENTIFIER ::= { enterprises 311 }
--      software        OBJECT IDENTIFIER ::= { microsoft 1 }
        internetServer  OBJECT IDENTIFIER ::= { software 7 }
        inetSrvCommon   OBJECT IDENTIFIER ::= { internetServer 1 }
        inetSrvStats    OBJECT IDENTIFIER ::= { inetSrvCommon 1 }

-- Internet Server Common Statistics

END
