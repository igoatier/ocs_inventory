-- *********************************************
-- Modified by Garth K. Williams
-- Williams Technology Consulting Services
-- Date: 14Aug2002
-- *********************************************
--  Modified for compatability with SNMP4W2K PERFMIB
-- *********************************************


NntpServer-MIB DEFINITIONS ::= BEGIN

    IMPORTS
	enterprises, Counter, TimeTicks
	    FROM RFC1155-SMI
    	OBJECT-TYPE
	    FROM RFC-1212
	DisplayString
	    FROM RFC1213-MIB
        internetServer
            FROM INTERNETSERVER-MIB;

--      microsoft       OBJECT IDENTIFIER ::= { enterprises 311 }
--      software        OBJECT IDENTIFIER ::= { microsoft 1 }
--      internetServer  OBJECT IDENTIFIER ::= { software 7 }
        nntpServer       OBJECT IDENTIFIER ::= { internetServer 6 }
        nntpStatistics   OBJECT IDENTIFIER ::= { nntpServer 1 }

-- NNTP Server Statistics

        totalBytesSentHighWord OBJECT-TYPE
                SYNTAX  Counter
                ACCESS  read-only
                STATUS  mandatory
                DESCRIPTION
                        "This is the high 32-bits of the total number of
                        of BYTEs sent by the NNTP Server"
                ::= { nntpStatistics 1 }

        totalBytesSentLowWord OBJECT-TYPE
                SYNTAX  Counter
                ACCESS  read-only
                STATUS  mandatory
                DESCRIPTION
                        "This is the low 32-bits of the total number of
                        of BYTEs sent by the NNTP Server"
                ::= { nntpStatistics 2 }

        totalBytesReceivedHighWord OBJECT-TYPE
                SYNTAX  Counter
                ACCESS  read-only
                STATUS  mandatory
                DESCRIPTION
                        "This is the high 32-bits of the total number of
                        of BYTEs received by the NNTP Server"
                ::= { nntpStatistics 3 }

        totalBytesReceivedLowWord OBJECT-TYPE
                SYNTAX  Counter
                ACCESS  read-only
                STATUS  mandatory
                DESCRIPTION
                        "This is the low 32-bits of the total number of
                        of BYTEs received by the NNTP Server"
                ::= { nntpStatistics 4 }

        totalConnections OBJECT-TYPE
                SYNTAX  Counter
                ACCESS  read-only
                STATUS  mandatory
                DESCRIPTION
                        "This is the total number of connections made to this
                        NNTP Server"
                ::= { nntpStatistics 5 }

        totalSslConnections OBJECT-TYPE
                SYNTAX  Counter
                ACCESS  read-only
                STATUS  mandatory
                DESCRIPTION
                        "This is the total number of SSL connections made
                         to this NNTP Server"
                ::= { nntpStatistics 6 }

        currentConnections OBJECT-TYPE
                SYNTAX  Counter
                ACCESS  read-only
                STATUS  mandatory
                DESCRIPTION
                        "This is the number of sessions currently
                        connected to the NNTP Server"
                ::= { nntpStatistics 7 }

        maxConnections OBJECT-TYPE
                SYNTAX  Counter
                ACCESS  read-only
                STATUS  mandatory
                DESCRIPTION
                        "This is the maximum number of users simulateously
                        connected to the NNTP Server"
                ::= { nntpStatistics 8 }

        logonAttempts OBJECT-TYPE
                SYNTAX  Counter
                ACCESS  read-only
                STATUS  mandatory
                DESCRIPTION
                        "This is the total number of logon attempts
                        against the NNTP Server"
                ::= { nntpStatistics 9 }

        logonFailures OBJECT-TYPE
                SYNTAX  Counter
                ACCESS  read-only
                STATUS  mandatory
                DESCRIPTION
                        "This is the total number of logon attempts
                        that failed against the NNTP Server"
                ::= { nntpStatistics 10 }

        currentAnonymousUsers OBJECT-TYPE
                SYNTAX  Counter
                ACCESS  read-only
                STATUS  mandatory
                DESCRIPTION
                        "This is the current number of anonymous users
                        connected to the NNTP Server"
                ::= { nntpStatistics 11 }

        currentNonAnonymousUsers OBJECT-TYPE
                SYNTAX  Counter
                ACCESS  read-only
                STATUS  mandatory
                DESCRIPTION
                        "This is the current number of nonanonymous users
                        connected to the NNTP Server"
                ::= { nntpStatistics 12 }

        totalAnonymousUsers OBJECT-TYPE
                SYNTAX  Counter
                ACCESS  read-only
                STATUS  mandatory
                DESCRIPTION
                        "This is the total number of anonymous users
                        connected to the NNTP Server"
                ::= { nntpStatistics 13 }

        totalNonAnonymousUsers OBJECT-TYPE
                SYNTAX  Counter
                ACCESS  read-only
                STATUS  mandatory
                DESCRIPTION
                        "This is the total number of nonanonymous users
                        connected to the NNTP Server"
                ::= { nntpStatistics 14 }

        maxAnonymousUsers OBJECT-TYPE
                SYNTAX  Counter
                ACCESS  read-only
                STATUS  mandatory
                DESCRIPTION
                        "This is the maximum number of anonymous users
                        simultaneously connected to the NNTP Server"
                ::= { nntpStatistics 15 }

        maxNonAnonymousUsers OBJECT-TYPE
                SYNTAX  Counter
                ACCESS  read-only
                STATUS  mandatory
                DESCRIPTION
                        "This is the maximum number of nonanonymous users
                        simultaneously connected to the NNTP Server"
                ::= { nntpStatistics 16 }

        totalOutboundConnects OBJECT-TYPE
                SYNTAX  Counter
                ACCESS  read-only
                STATUS  mandatory
                DESCRIPTION
                        "This is the total number of outbound connections
                        that have been made by the NNTP Server"
                ::= { nntpStatistics 17 }

        outboundConnectFailures OBJECT-TYPE
                SYNTAX  Counter
                ACCESS  read-only
                STATUS  mandatory
                DESCRIPTION
                        "This is the total number of failed outbound
                        connections made by the NNTP Server"
                ::= { nntpStatistics 18 }

        currentOutboundConnects OBJECT-TYPE
                SYNTAX  Counter
                ACCESS  read-only
                STATUS  mandatory
                DESCRIPTION
                        "This is the current number of outbound connections
                        made by the NNTP Server"
                ::= { nntpStatistics 19 }

        outboundLogonFailures OBJECT-TYPE
                SYNTAX  Counter
                ACCESS  read-only
                STATUS  mandatory
                DESCRIPTION
                        "This is the total number of failed outbound logons
                        made by the NNTP Server"
                ::= { nntpStatistics 20 }

        totalPushFeeds OBJECT-TYPE
                SYNTAX  Counter
                ACCESS  read-only
                STATUS  mandatory
                DESCRIPTION
                        "This is the total number of push feeds
                        made by the NNTP Server"
                ::= { nntpStatistics 21 }

        totalPullFeeds OBJECT-TYPE
                SYNTAX  Counter
                ACCESS  read-only
                STATUS  mandatory
                DESCRIPTION
                        "This is the total number of pull feeds
                        made to the NNTP Server"
                ::= { nntpStatistics 22 }

        totalPassiveFeeds OBJECT-TYPE
                SYNTAX  Counter
                ACCESS  read-only
                STATUS  mandatory
                DESCRIPTION
                        "This is the total number of passive feeds
                        accepted by the NNTP Server"
                ::= { nntpStatistics 23 }

        totalArticlesSent OBJECT-TYPE
                SYNTAX  Counter
                ACCESS  read-only
                STATUS  mandatory
                DESCRIPTION
                        "This is the total number of articles sent
                        by the NNTP Server"
                ::= { nntpStatistics 24 }

        totalArticlesReceived OBJECT-TYPE
                SYNTAX  Counter
                ACCESS  read-only
                STATUS  mandatory
                DESCRIPTION
                        "This is the total number of articles received
                        by the NNTP Server"
                ::= { nntpStatistics 25 }

        totalArticlesPosted OBJECT-TYPE
                SYNTAX  Counter
                ACCESS  read-only
                STATUS  mandatory
                DESCRIPTION
                        "This is the total number of articles posted
                        to the NNTP Server"
                ::= { nntpStatistics 26 }

        currentArticleMapEntries OBJECT-TYPE
                SYNTAX  Counter
                ACCESS  read-only
                STATUS  mandatory
                DESCRIPTION
                        "This is the current number of entries in the
                        article mapping table the NNTP Server"
                ::= { nntpStatistics 27 }

        currentHistoryMapEntries OBJECT-TYPE
                SYNTAX  Counter
                ACCESS  read-only
                STATUS  mandatory
                DESCRIPTION
                        "This is the current number of entries in the
                        history mapping table the NNTP Server"
                ::= { nntpStatistics 28 }

        currentXoverEntries OBJECT-TYPE
                SYNTAX  Counter
                ACCESS  read-only
                STATUS  mandatory
                DESCRIPTION
                        "This is the current number of entries in the
                        XOVER table the NNTP Server"
                ::= { nntpStatistics 29 }

        currentSessionsFlowControlled OBJECT-TYPE
                SYNTAX  Counter
                ACCESS  read-only
                STATUS  mandatory
                DESCRIPTION
                        "This is the current number of sessions in the
                        flow control state for the NNTP Server"
                ::= { nntpStatistics 30 }

        totalArticlesExpired OBJECT-TYPE
                SYNTAX  Counter
                ACCESS  read-only
                STATUS  mandatory
                DESCRIPTION
                        "This is the total number of articles expired
                        by the NNTP Server"
                ::= { nntpStatistics 31 }

        totalControlMessagesIn OBJECT-TYPE
                SYNTAX  Counter
                ACCESS  read-only
                STATUS  mandatory
                DESCRIPTION
                        "This is the total number of control messages received
                        by the NNTP Server"
                ::= { nntpStatistics 32 }

        totalControlMessagesFailed OBJECT-TYPE
                SYNTAX  Counter
                ACCESS  read-only
                STATUS  mandatory
                DESCRIPTION
                        "This is the total number of control messages failed or not applied
                        by the NNTP Server"
                ::= { nntpStatistics 33 }

        totalModeratedPostingsSent OBJECT-TYPE
                SYNTAX  Counter
                ACCESS  read-only
                STATUS  mandatory
                DESCRIPTION
                        "This is the total number of moderated postings the NNTP Server 
                        attempts to send to an SMTP Server"
                ::= { nntpStatistics 34 }

        totalModeratedPostingsFailed OBJECT-TYPE
                SYNTAX  Counter
                ACCESS  read-only
                STATUS  mandatory
                DESCRIPTION
                        "This is the total number of moderated postings the NNTP Server
                        fails to send to an SMTP Server"
                ::= { nntpStatistics 35 }

        totalArticleCommands OBJECT-TYPE
                SYNTAX  Counter
                ACCESS  read-only
                STATUS  mandatory
                DESCRIPTION
                        "This is the total number of ARTICLE commands received
                        by the NNTP Server"
                ::= { nntpStatistics 36 }

        totalGroupCommands OBJECT-TYPE
                SYNTAX  Counter
                ACCESS  read-only
                STATUS  mandatory
                DESCRIPTION
                        "This is the total number of GROUP commands received
                        by the NNTP Server"
                ::= { nntpStatistics 37 }

        totalHelpCommands OBJECT-TYPE
                SYNTAX  Counter
                ACCESS  read-only
                STATUS  mandatory
                DESCRIPTION
                        "This is the total number of HELP commands received
                        by the NNTP Server"
                ::= { nntpStatistics 38 }

        totalIHaveCommands OBJECT-TYPE
                SYNTAX  Counter
                ACCESS  read-only
                STATUS  mandatory
                DESCRIPTION
                        "This is the total number of IHAVE commands received
                        by the NNTP Server"
                ::= { nntpStatistics 39 }

        totalLastCommands OBJECT-TYPE
                SYNTAX  Counter
                ACCESS  read-only
                STATUS  mandatory
                DESCRIPTION
                        "This is the total number of LAST commands received
                        by the NNTP Server"
                ::= { nntpStatistics 40 }

        totalListCommands OBJECT-TYPE
                SYNTAX  Counter
                ACCESS  read-only
                STATUS  mandatory
                DESCRIPTION
                        "This is the total number of LIST commands received
                        by the NNTP Server"
                ::= { nntpStatistics 41 }

        totalNewgroupsCommands OBJECT-TYPE
                SYNTAX  Counter
                ACCESS  read-only
                STATUS  mandatory
                DESCRIPTION
                        "This is the total number of NEWGROUPS commands received
                        by the NNTP Server"
                ::= { nntpStatistics 42 }

        totalNewnewsCommands OBJECT-TYPE
                SYNTAX  Counter
                ACCESS  read-only
                STATUS  mandatory
                DESCRIPTION
                        "This is the total number of NEWNEWS commands received
                        by the NNTP Server"
                ::= { nntpStatistics 43 }

        totalNextCommands OBJECT-TYPE
                SYNTAX  Counter
                ACCESS  read-only
                STATUS  mandatory
                DESCRIPTION
                        "This is the total number of NEXT commands received
                        by the NNTP Server"
                ::= { nntpStatistics 44 }

        totalPostCommands OBJECT-TYPE
                SYNTAX  Counter
                ACCESS  read-only
                STATUS  mandatory
                DESCRIPTION
                        "This is the total number of POST commands received
                        by the NNTP Server"
                ::= { nntpStatistics 45 }

        totalQuitCommands OBJECT-TYPE
                SYNTAX  Counter
                ACCESS  read-only
                STATUS  mandatory
                DESCRIPTION
                        "This is the total number of QUIT commands received
                        by the NNTP Server"
                ::= { nntpStatistics 46 }

        totalStatCommands OBJECT-TYPE
                SYNTAX  Counter
                ACCESS  read-only
                STATUS  mandatory
                DESCRIPTION
                        "This is the total number of STAT commands received
                        by the NNTP Server"
                ::= { nntpStatistics 47 }

        totalCheckCommands OBJECT-TYPE
                SYNTAX  Counter
                ACCESS  read-only
                STATUS  mandatory
                DESCRIPTION
                        "This is the total number of CHECK commands received
                        by the NNTP Server"
                ::= { nntpStatistics 48 }

        totalTakethisCommands OBJECT-TYPE
                SYNTAX  Counter
                ACCESS  read-only
                STATUS  mandatory
                DESCRIPTION
                        "This is the total number of TAKETHIS commands received
                        by the NNTP Server"
                ::= { nntpStatistics 49 }

        totalModeCommands OBJECT-TYPE
                SYNTAX  Counter
                ACCESS  read-only
                STATUS  mandatory
                DESCRIPTION
                        "This is the total number of MODE commands received
                        by the NNTP Server"
                ::= { nntpStatistics 50 }

        totalSearchCommands OBJECT-TYPE
                SYNTAX  Counter
                ACCESS  read-only
                STATUS  mandatory
                DESCRIPTION
                        "This is the total number of SEARCH commands received
                        by the NNTP Server"
                ::= { nntpStatistics 51 }

        totalXHdrCommands OBJECT-TYPE
                SYNTAX  Counter
                ACCESS  read-only
                STATUS  mandatory
                DESCRIPTION
                        "This is the total number of XHDR commands received
                        by the NNTP Server"
                ::= { nntpStatistics 52 }

        totalXOverCommands OBJECT-TYPE
                SYNTAX  Counter
                ACCESS  read-only
                STATUS  mandatory
                DESCRIPTION
                        "This is the total number of XOVER commands received
                        by the NNTP Server"
                ::= { nntpStatistics 53 }

        totalXPatCommands OBJECT-TYPE
                SYNTAX  Counter
                ACCESS  read-only
                STATUS  mandatory
                DESCRIPTION
                        "This is the total number of XPAT commands received
                        by the NNTP Server"
                ::= { nntpStatistics 54 }

        totalXReplicCommands OBJECT-TYPE
                SYNTAX  Counter
                ACCESS  read-only
                STATUS  mandatory
                DESCRIPTION
                        "This is the total number of XREPLIC commands received
                        by the NNTP Server"
                ::= { nntpStatistics 55 }

END
